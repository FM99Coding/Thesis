module ietf-inet-types {
  yang-version 1.1;
  namespace "urn:ietf:params:xml:ns:yang:ietf-inet-types";
  prefix "inet";

  organization "UNIVERSITA' DELLA CALABRIA - Master Degree in Telecommunication 
                Engineering, Smart Sensing, Computing, and Networking - TITAN Lab";
  contact "Course Web: <https://corsi.unical.it/lm/telecommunicationengineering-smart-
                        sensing-computing-and-networking/ >
           Editor: Francesco Mazzei <mailto:francesco1999mazzei@gmail.com>
           Supervisor: Pasquale Pace <mailto: p.pace@dimes.unical.it>
           Supervisor: Antonio Iera <mailto: antonio.iera@dimes.unical.it>";
  description "This module contains a collection of generally useful derived YANG data 
               types for Internet addresses and related things.

               This YANG module has been developed as part of the Master's Thesis in 
               Telecommunication Engineering at the University of Calabria. The model 
               is based on and modifies the module defined in RFC 6991(IETF NETMOD 
               Working Group), preserving the original structure and introducing 
               extensions/adaptations for the purposes of this research.

               Copyright (c) 2022 IETF Trust and the persons identified as authors of 
               the code. All rights reserved. Redistribution and use in source and 
               binary forms, with or without modification, is permitted pursuant to, 
               and subject to the license terms contained in, the Simplified BSD 
               License set forth in Section 4.c of the IETF Trust's Legal Provisions 
               Relating to IETF Documents(https://trustee.ietf.org/license-info).";

  revision 2025-10-06 {
    description "Elements considered non-essential for the objectives of the Master's 
                 Thesis have been omitted. The original structure and semantics have 
                 been preserved where applicable.";
  }
  revision 2023-01-23 {
    description "Added new data types. Several pattern statements have been improved.";
    reference "RFC 6991: Common YANG Data Types";
  }
  revision 2013-07-15 {
    description "Added new data types.";    
    reference "RFC 6991: Common YANG Data Types";
  }
  revision 2010-09-24 {
    description "Initial revision.";
    reference "RFC 6021: Common YANG Data Types";
  }
  
  typedef ipv4-address {
    type string {
      pattern '(([0-9]|[1-9][0-9]|1[0-9][0-9]|2[0-4][0-9]|25[0-5])\.){3}'+
              '([0-9]|[1-9][0-9]|1[0-9][0-9]|2[0-4][0-9]|25[0-5])'+
              '(%[A-Za-z0-9][A-Za-z0-9\-\._~/]*)?';
    }
    description "This type represents an IPv4 address in dotted-quad notation.  The  
                 IPv4 address may include a zone index, separated by a % sign. The zone 
                 index is used to disambiguate identical address values.  For link-
                 local addresses, the zone index will typically be the interface index 
                 number or the name of an interface.  If the zone index is not present, 
                 the default zone of the device will be used. The canonical format for          
                 the zone index is the numerical format";
  }


  typedef ipv4-address-no-zone {
    type inet:ipv4-address {
      pattern '[0-9\.]*';
    }
    description "An IPv4 address without a zone index.";
  }

  typedef uri {
    type string {
      pattern '[a-z][a-z0-9+.-]*:.*';
    }
    description "The uri type represents a Uniform Resource Identifier (URI) as defined 
                 by the rule 'URI' in RFC 3986. Objects using the uri type MUST be in 
                 US-ASCII encoding. All unnecessary percent-encoding is removed, and 
                 all case-insensitive characters are set to lowercase except for 
                 hexadecimal digits, which are normalized to uppercase. Objects using 
                 the uri type may restrict the schemes that they permit. A zero-length 
                 URI is not a valid URI.";
    reference "RFC 3986: Uniform Resource Identifier (URI): Generic Syntax
               RFC 3305: Report from the Joint W3C/IETF URI Planning Interest Group: 
                         Uniform Resource Identifiers (URIs), URLs, and Uniform 
                         Resource Names (URNs): Clarifications and Recommendations
               RFC 5017: MIB Textual Conventions for Uniform Resource Identifiers 
                         (URIs)";
  }
} //module ietf-inet-types
