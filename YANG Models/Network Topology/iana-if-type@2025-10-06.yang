module iana-if-type {
  yang-version 1.1;
  namespace "urn:ietf:params:xml:ns:yang:iana-if-type";
  prefix ianaift;

  import ietf-interfaces {
    prefix if;
    reference "RFC 8343: A YANG Data Model for Interface Management";
  }

  organization "UNIVERSITA' DELLA CALABRIA - Master Degree in Telecommunication 
                Engineering, Smart Sensing, Computing, and Networking - TITAN Lab";
  contact "Course Web: <https://corsi.unical.it/lm/telecommunicationengineering-smart-
                        sensing-computing-and-networking/ >
           Editor: Francesco Mazzei <mailto:francesco1999mazzei@gmail.com>
           Supervisor: Pasquale Pace <mailto: p.pace@dimes.unical.it>
           Supervisor: Antonio Iera <mailto: antonio.iera@dimes.unical.it>";
  description "This YANG module defines YANG identities for IANA-registered interface 
               types.

               This YANG module has been developed as part of the Master's Thesis
               in Telecommunication Engineering at the University of Calabria. The 
               model is based on and modifies the module defined in RFC 7224(IANA), 
               preserving the original structure and introducing extensions/adaptations 
               for the purposes of this research.

               Copyright (c) 2014 IETF Trust and the persons identified as authors of 
               the code. All rights reserved. Redistribution and use in source and 
               binary forms, with or without modification, is permitted pursuant to, 
               and subject to the license terms contained in, the Simplified BSD 
                License set forth in Section 4.c of the IETF Trust's Legal Provisions 
               Relating to IETF Documents(https://trustee.ietf.org/license-info).";
  reference "IANA 'ifType definitions' registry. <http://www.iana.org/assignments/smi-numbers>";

  revision 2025-10-06 {
    description "Elements considered non-essential for the objectives of the Master's 
                 Thesis have been omitted. The original structure and semantics have 
                 been preserved where applicable.";
  }
  revision 2023-01-26 {  }
  revision 2022-08-24 {  }
  revision 2022-08-17 {  }
  revision 2022-03-07 {  }
  revision 2021-06-21 {  }
  revision 2021-05-17 {  }
  revision 2021-04-22 {  }
  revision 2021-04-01 {  }
  revision 2021-02-18 {  }
  revision 2020-08-27 {  }
  revision 2020-07-13 {  }
  revision 2020-07-10 {  }
  revision 2020-01-10 {  }
  revision 2019-10-16 {  }
  revision 2019-07-16 {  }
  revision 2019-06-21 {  }
  revision 2019-02-08 {  }
  revision 2019-01-31 {  }
  revision 2018-07-03 {  }
  revision 2018-06-29 {  }
  revision 2018-06-28 {  }
  revision 2018-06-22 {  }
  revision 2018-06-21 {  }
  revision 2017-03-30 {  }
  revision 2017-01-19 {  }
  revision 2016-11-23 {  }
  revision 2016-06-09 {  }
  revision 2016-05-03 {  }
  revision 2015-06-12 {  }  
  revision 2014-09-24 {  }
  revision 2014-09-19 {  }
  revision 2014-07-03 {  }
  revision 2014-05-19 {  }
  revision 2014-05-08 {
    description "Initial revision.";
    reference "RFC 7224: IANA Interface Type YANG Module";
  }

  identity iana-interface-type {
    base if:interface-type;
    description "This identity is used as a base for all interface types defined in the 
                'ifType definitions' registry.";
  }
  
  identity ethernetCsmacd {
    base iana-interface-type;
    description "For all Ethernet-like interfaces, regardless of speed.";
    reference "RFC 3635 - Definitions of Managed Objects for the Ethernet-like 
               Interface Types";
  }

  identity ieee80211 {
    base iana-interface-type;
    description "Radio spread spectrum.";
  }

  identity radioMAC {
    base iana-interface-type;
    description "MAC layer over radio links.";
  }

  identity microwaveRadioLinkTerminal {
    base iana-interface-type;
    description "radio link interface for one or several aggregated microwave 
                 carriers.";
    reference "RFC 8561 - A YANG Data Model for Microwave Radio Link";
  }

  identity microwaveCarrierTermination {
    base iana-interface-type;
    description "air interface of a single microwave carrier.";
    reference "RFC 8561 - A YANG Data Model for Microwave Radio Link";
  }

  identity cpri {
    base iana-interface-type;
    description "Common Public Radio Interface.";
    reference "CPRI v7.0";
  }

  identity roe {
    base iana-interface-type;
    description "Radio over Ethernet Interface.";
    reference "1914.3-2018 - IEEE Standard for Radio over Ethernet Encapsulations and 
               Mappings";
  }

  identity ip {
    base iana-interface-type;
    description "IP (for APPN HPR in IP networks).";
  }

  identity l3ipvlan {
    base iana-interface-type;
    description "Layer 3 Virtual LAN using IP.";
  }
  
  identity tunnel {
    base iana-interface-type;
    description "Encapsulation interface.";
  }
  
  identity softwareLoopback {
    base iana-interface-type;
  }
} //module iana-if-types
