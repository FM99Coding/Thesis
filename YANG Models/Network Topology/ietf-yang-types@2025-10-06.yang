module ietf-yang-types {
  yang-version 1.1;
  namespace "urn:ietf:params:xml:ns:yang:ietf-yang-types";
  prefix "yang";

  organization "UNIVERSITA' - DELLA CALABRIA - Master Degree in Telecommunication 
                Engineering, Smart Sensing, Computing, and Networking - TITAN Lab";
  contact "Course Web: <https://corsi.unical.it/lm/telecommunicationengineering-smart-
                        sensing-computing-and-networking/ >
           Editor: Francesco Mazzei <mailto:francesco1999mazzei@gmail.com>
           Supervisor: Pasquale Pace <mailto: p.pace@dimes.unical.it>
           Supervisor: Antonio Iera <mailto: antonio.iera@dimes.unical.it>";
  description "This module contains a collection of generally useful derived YANG data 
               types.
    
               This YANG module has been developed as part of the Master's Thesis
               in Telecommunication Engineering at the University of Calabria. The 
               model is based on and modifies the module defined in RFC 6991 (IETF 
               NETMOD Working Group), preserving the original structure and introducing 
               extensions/adaptations for the purposes of this research.

               Copyright (c) 2022 IETF Trust and the persons identified as authors of 
               the code. All rights reserved. Redistribution and use in source and 
               binary forms, with or without modification, is permitted pursuant to, 
               and subject to the license terms contained in, the Simplified BSD 
               License set forth in Section 4.c of the IETF Trust's Legal Provisions 
               Relating to IETF Documents(https://trustee.ietf.org/license-info).";

  revision 2025-10-06 {
    description "Elements considered non-essential for the objectives of the Master's 
                 Thesis have been omitted. The original structure and semantics have 
                 been preserved where applicable.";
  }
  revision 2023-01-23 {
    description "Added new data types. The yang-identifier definition has been aligned 
                 with YANG 1.1. Several pattern statements have been improved.";
    reference "RFC 6991: Common YANG Data Types";
  }
  revision 2013-07-15 {
    description "Added new data types.";
    reference "RFC 6991: Common YANG Data Types";
  }
  revision 2010-09-24 {
    description "Initial revision.";
    reference "RFC 6021: Common YANG Data Types";
  }

  typedef counter32 {
    type uint32;
    description "Non-negative integer that monotonically increases until it reaches a
                 maximum value of 2^32-1 (4294967295 decimal), when it wraps around and 
                 starts increasing again from zero.";
    reference "RFC 2578: Structure of Management Information Version 2 (SMIv2)";
  }

  typedef counter64 {
    type uint64;
    description "Non-negative integer that monotonically increases until it reaches a
                 maximum value of 2^64-1 (18446744073709551615 decimal), when it wraps 
                 around and starts increasing again from zero.";
    reference "RFC 2578: Structure of Management Information Version 2 (SMIv2)";
  }

  typedef gauge64 {
    type uint64;
    description
     "Non-negative integer, which may increase or decrease, but shall never exceed a 
      maximum value, nor fall below a minimum value.  The maximum value cannot be 
      greater than 2^64-1 (18446744073709551615), and the minimum value cannot be 
      smaller than 0.";
    reference "RFC 2856: Textual Conventions for Additional High Capacity Data Types";
  }

  typedef date-and-time {
    type string {
      pattern '[0-9]{4}-(1[0-2]|0[1-9])-(0[1-9]|[1-2][0-9]|3[0-1])'
            + 'T(0[0-9]|1[0-9]|2[0-3]):[0-5][0-9]:[0-5][0-9](\.[0-9]+)?'
            + '(Z|[\+\-]((1[0-3]|0[0-9]):([0-5][0-9])|14:00))?';
    }
    description "The date-and-time type is a profile of the ISO 8601 standard for 
                 representation of dates and times using the Gregorian calendar.";
    reference "RFC 3339: Date and Time on the Internet: Timestamps
               RFC 2579: Textual Conventions for SMIv2 XSD-TYPES: XML Schema Definition  
                         Language (XSD) 1.1 Part 2: Datatypes";
  }

  typedef phys-address {
    type string {
      pattern '([0-9a-fA-F]{2}(:[0-9a-fA-F]{2})*)?';
    }
    description "Represents media-or physical-level addresses represented as a sequence 
                 octets, each octet represented by two hexadecimal numbers. Octets are 
                 separated by colons. The canonical representation uses lowercase 
                 characters.";
    reference "RFC 2579: Textual Conventions for SMIv2";
  }

  typedef dotted-quad {
    type string {
      pattern
        '(([0-9]|[1-9][0-9]|1[0-9][0-9]|2[0-4][0-9]|25[0-5])\.){3}'
      + '([0-9]|[1-9][0-9]|1[0-9][0-9]|2[0-4][0-9]|25[0-5])';
    }
    description "An unsigned 32-bit number expressed in the dotted-quad notation, i.e., 
                 four octets written as decimal numbers and separated with the '.' 
                 (full stop) character.";
  }
} //module ietf-yang-types
