module ietf-microwave-radio-link {
  yang-version 1.1;
  namespace "urn:ietf:params:xml:ns:yang:ietf-microwave-radio-link";
  prefix mrl;

  import iana-if-type {
    prefix ianaift;
    reference "RFC 7224: IANA Interface Type YANG Module";
  }
  import ietf-interfaces {
    prefix if;
    reference "RFC 8343: A YANG Data Model for Interface Management";
  }
  import ietf-microwave-types {
    prefix mw-types;
    reference "RFC 8561: A YANG Data Model for Microwave Radio Link";
  }
  import time-record-fields {
    prefix trf;
  }

  organization "UNIVERSITA? DELLA CALABRIA - Master Degree in Telecommunication 
                Engineering, Smart Sensing, Computing, and Networking - TITAN Lab";
  contact "Course Web: <https://corsi.unical.it/lm/telecommunicationengineering-smart-
                        sensing-computing-and-networking/ >
           Editor: Francesco Mazzei <mailto:francesco1999mazzei@gmail.com>
           Supervisor: Pasquale Pace <mailto: p.pace@dimes.unical.it>
           Supervisor: Antonio Iera <mailto: antonio.iera@dimes.unical.it>";
  description "This is a module for the entities in a generic microwave system.
     
               This YANG module has been developed as part of the Master's Thesis in 
               Telecommunication Engineering at the University of Calabria. The model 
               is based on and modifies the module defined in RFC 8561 (IETF CCAMP 
               Working Group), preserving the original structure and introducing 
               extensions/adaptations for the purposes of this research.

               Copyright (c) 2019 IETF Trust and the persons identified as authors of 
               the code. All rights reserved. Redistribution and use in source and 
               binary forms, with or without modification, is permitted pursuant to, 
               and subject to the license terms contained in, the Simplified BSD 
               License set forth in Section 4.c of the IETF Trust's Legal Provisions 
               Relating to IETF Documents(https://trustee.ietf.org/license-info).";

  revision 2025-10-04 {
    description "Elements considered non-essential for the objectives of the Master's 
                 Thesis have been omitted. The original structure and semantics have 
                 been preserved where applicable.";
  }
  revision 2019-06-19 {
    description "Initial revision.";
    reference "RFC 8561: A YANG Data Model for Microwave Radio Link";
  }

  typedef power {
    type decimal64 {
      fraction-digits 2;
    }
    description "Type used for the power values in the data nodes.";
  }

  augment "/if:interfaces/if:interface" {
    when "derived-from-or-self(if:type," + "'ianaift:microwaveRadioLinkTerminal')";
    description "Addition of data nodes for the radio link terminal to the standard 
                 Interface data model.";
          
    leaf-list carrier-terminations {
      type if:interface-ref;
      must "derived-from-or-self(/if:interfaces/if:interface"
            +"[if:name = current()]"
            +"/if:type,'ianaift:microwaveCarrierTermination')" {
        description "The type of interface must be 'microwaveCarrierTermination'.";
      }
      min-elements 1;
      description "A list of references to carrier terminations included in the 
                   radio link terminal.";
    }
  } //augment "/if:interfaces/if:interface"

  augment "/if:interfaces/if:interface" {
    when "derived-from-or-self(if:type,"+"'ianaift:microwaveCarrierTermination')";
    description "Addition of data nodes for carrier termination to the standard 
                 Interface data model.";

    leaf carrier-id {
      type string;
      description "ID of the carrier.";
    }
 
    leaf tx-enabled {
      type boolean;
      default "false";
      description "Disables (false) or enables (true) the transmitter. Only 
                   applicable when the interface is enabled (interface:enabled=true).";
    }

    leaf tx-oper-status {
      type enumeration {
        enum off {
          description "Transmitter is off.";
        }
        enum on {
          description "Transmitter is on.";
        }
        enum standby {
          description "Transmitter is in standby.";
        }
      } //type enumeration
      config false;
      description "Shows the operative status of the transmitter.";
    } //leaf tx-oper-status

    leaf tx-frequency {
      type uint32;
      units "kHz";
      mandatory true;
      description "Selected transmitter frequency.";
    }
    choice freq-or-distance {
      leaf rx-frequency {
        type uint32;
        units "kHz";
        description "Selected receiver frequency.";
      }
      leaf duplex-distance {
        type int32;
        units "kHz";
        description "Distance between transmitter and receiver frequencies.";
      }
      mandatory true;
    } //choice freq-or-distance

    leaf channel-separation {
      type uint32;
      units "kHz";
      mandatory true;
      description "The amount of bandwidth allocated to a carrier.";
      reference "ETSI EN 302 217-1";
    }

    leaf actual-transmitted-level {
      type power {
        range "-99..99";
      }
      units "dBm";
      config false;
      description "Actual transmitted power level (0.1 dBm resolution).";
      reference "ETSI EN 301 129";
    }

    leaf actual-received-level {
      type power {
        range "-99..-20";
      }
      units "dBm";
      config false;
      description "Actual received power level (0.1 dBm resolution).";
      reference "ETSI EN 301 129";
    }

    choice coding-modulation-mode {
      container single {
        description "A single modulation order only.";
        reference "ETSI EN 302 217-1";

        leaf selected-cm {
          type identityref {
            base mw-types:coding-modulation;
          }
          mandatory true;
          description "Selected the single coding/modulation.";
        }
      } //container single

      container adaptive {
        description "Adaptive coding/modulation.";
        reference "ETSI EN 302 217-1";

        leaf selected-min-acm {
          type identityref {
            base mw-types:coding-modulation;
          }
          mandatory true;
          description "Selected minimum coding/modulation.";
        } //leaf selected-min-acm

        leaf selected-max-acm {
          type identityref {
            base mw-types:coding-modulation;
          }
          mandatory true;
          description "Selected maximum coding/modulation";
        }
      } //container adaptive
      mandatory true;
      description "A selection of single or adaptive coding/modulation mode.";
    } //choice coding-modulation-mode

    leaf actual-snir {
      type decimal64 {
        fraction-digits 1;
        range "0..99";
      }
      units "dB";
      config false;
      description "Actual signal to noise plus the interference ratio (0.1 dB).";
    }

    container time-records {     
      uses trf:time-records;
    }

    container capabilities {
      config false;
      description "Capabilities of the installed equipment.";
  
      leaf min-tx-frequency {
        type uint32;
        units "kHz";
        description "Minimum Tx frequency possible to use.";
      }
      leaf max-tx-frequency {
        type uint32;
        units "kHz";
        description "Maximum Tx frequency possible to use.";
      }
      leaf min-rx-frequency {
        type uint32;
        units "kHz";
        description "Minimum Rx frequency possible to use.";
      }
      leaf max-rx-frequency {
        type uint32;
        units "kHz";
        description "Maximum Tx frequency possible to use.";
      }
      
      container time-records {     
        uses trf:time-records;
      }
    } //container capabilities

    container radio-performance-statistics {
      config false;
      description "ETSI EN 301 129 radio physical interface statistics relevant
                   for a carrier termination.";

      leaf min-rltm {
        type power {
          range "-99..-20";
        }
        units "dBm";
        description "Minimum received power level.";
        reference "ETSI EN 301 129";
      }

      leaf max-rltm {
        type power {
          range "-99..-20";
        }
        units "dBm";
        description "Maximum received power level.";
        reference "ETSI EN 301 129";
      }

      leaf min-tltm {
        type power {
          range "-99..99";
        }
        units "dBm";
        description "Minimum transmitted power level.";
        reference "ETSI EN 301 129";
      }

      leaf max-tltm {
        type power {
          range "-99..99";
        }
        units "dBm";
        description "Maximum transmitted power level.";
        reference "ETSI EN 301 129";
      }
      
      container time-records {     
        uses trf:time-records;
      }
    } //container radio-performance-statistics
  } //augment "/if:interfaces/if:interface"
} //module ietf-microwave-radio-link
