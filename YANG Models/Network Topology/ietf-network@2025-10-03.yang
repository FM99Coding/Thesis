module ietf-network {
  yang-version 1.1;
  namespace "urn:ietf:params:xml:ns:yang:ietf-network";
  prefix nw;

  import ietf-inet-types {
    prefix inet;
    reference "RFC 6991: Common YANG Data Types";
  }
  import time-record-fields {
    prefix trf;
  }

  organization "UNIVERSITA' DELLA CALABRIA - Master Degree in Telecommunication 
                Engineering, Smart Sensing, Computing, and Networking - TITAN Lab";
  contact "Course Web: <https://corsi.unical.it/lm/telecommunicationengineering-smart-
                        sensing-computing-and-networking/ >
           Editor: Francesco Mazzei <mailto:francesco1999mazzei@gmail.com>
           Supervisor: Pasquale Pace <mailto: p.pace@dimes.unical.it>
           Supervisor: Antonio Iera <mailto: antonio.iera@dimes.unical.it>";
  description "This module contains the definition of a common base data model for a 
               collection of nodes in a network. 

	       This YANG module has been developed as part of the Master's Thesis
               in Telecommunication Engineering at the University of Calabria. The 
               model is based on and modifies the module defined in RFC 8345 (IETF I2RS 
               Working Group), preserving the original structure and introducing 
               extensions/adaptations for the purposes of this research.

               Copyright (c) 2018 IETF Trust and the persons identified as authors of 
               the code. All rights reserved. Redistribution and use in source and 
               binary forms, with or without modification, is permitted pursuant to, 
               and subject to the license terms contained in, the Simplified BSD 
               License set forth in Section 4.c of the IETF Trust's Legal Provisions 
               Relating to IETF Documents(https://trustee.ietf.org/license-info).";

  revision 2025-10-03 {
    description "Elements considered non-essential for the objectives of the Master's 
                 Thesis have been omitted. The original structure and semantics have 
                 been preserved where applicable.";
  }
  revision 2018-02-26 {
    description "Initial revision.";
    reference "RFC 8345: A YANG Data Model for Network Topologies";
  }

  typedef node-id {
    type inet:uri;
    description "Identifier for a node.";
  }
  typedef network-id {
    type inet:uri;
    description "Identifier for a network.";
  }

  grouping network-ref {
    description "Contains the information necessary to reference a network.";
    leaf network-ref {
      type leafref {
        path "/nw:networks/nw:network/nw:network-id";
        require-instance false;
      }
    }
  }

  grouping node-ref {
    description "Contains the information necessary to reference a node.";
    leaf node-ref {
      type leafref {
        path "/nw:networks/nw:network[nw:network-id=current()/../"+
             "network-ref]/nw:node/nw:node-id";
        require-instance false;
      }
      description "Nodes are identified relative to the network that contains them.";
    }
    uses network-ref;
  }

  container networks {
    description "Serves as a top-level container for a list of networks.";
    list network {
      key "network-id";
      description "Describes a network. A network typically contains an inventory of 
                   nodes and topological information.";

      leaf network-id {
        type network-id;
        description "Identifies a network.";
      }

      container network-types {
        description "Augmentation target. The network type is indicated through 
                     corresponding presence containers augmented into this container.";
      }

      list node {
        key "node-id";
        description "The inventory of nodes of this network.";

        leaf node-id {
          type node-id;
          description "Uniquely identifies a node within the containing network.";
        }
        
        container time-records {     
          uses trf:time-records;
        }
      } //list node
    } //list network
    
    container time-records {     
      uses trf:time-records;
    }
  } //container networks
} //module ietf-network
